Language="VBSCRIPT"
' ListDesignModeParts.CATScript
' Lists which parts in the active product are currently loaded in Design Mode
' (the heavy ones). Read-only.
' Heuristic: a leaf whose PartDocument.Part is reachable is in Design Mode.

Option Explicit

Dim heavy, total

Sub CATMain()
    Dim doc
    Set doc = CATIA.ActiveDocument
    If TypeName(doc) <> "ProductDocument" Then
        MsgBox "Open a product (assembly).", vbExclamation
        Exit Sub
    End If
    heavy = "": total = 0
    Walk doc.Product
    If heavy = "" Then
        MsgBox "No parts are in Design Mode. Everything is lightweight.", vbInformation
    Else
        MsgBox total & " part(s) in Design Mode:" & vbCrLf & vbCrLf & heavy, vbInformation, "ListDesignModeParts"
    End If
End Sub

Sub Walk(prod)
    Dim n, i
    On Error Resume Next
    n = prod.Products.Count
    If Err.Number <> 0 Then n = 0: Err.Clear
    If n = 0 Then
        Dim p
        Set p = prod.ReferenceProduct.Parent.Part
        If Err.Number = 0 And Not p Is Nothing Then
            total = total + 1
            If total <= 40 Then heavy = heavy & prod.PartNumber & " (" & prod.Name & ")" & vbCrLf
        End If
        Err.Clear
    End If
    On Error GoTo 0
    For i = 1 To n
        Walk prod.Products.Item(i)
    Next
End Sub
